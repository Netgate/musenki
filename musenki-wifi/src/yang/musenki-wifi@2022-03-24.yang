module musenki-wifi{
    yang-version 1.1;
    namespace "urn:example:musenki:wifi";
    prefix wifi;
    import openconfig-access-points {
	description "Top level WiFi model for a list of Access Points
                     Adds the following top-level config objects:
                       access-points, components, joined-aps, messages,
                       provision-aps, radios, ssids, system ";
	prefix access-points;
	}
    import openconfig-ap-manager {
	description 
	    "Top level configuration and state data for a system which manages
             Access Points.
             Adds the following top-level config objects:
               joined-aps               provision-aps";
	prefix ap-manager;
    }
    import ietf-netconf-acm {
	prefix nacm;
    }
    revision 2022-03-24 {
	description
	    "Renamed to musenki-wifi, added NACM";
    }
    revision 2021-06-22 {
	description
	    "Initial top-level wifi openconfig version";
    }
}
